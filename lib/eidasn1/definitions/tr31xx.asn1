--
-- Copyright (C) 2012 Bundesdruckerei GmbH
--

TR31XX DEFINITIONS ::=

BEGIN


bsi-de OBJECT IDENTIFIER ::= { itu-t(0) identified-organization(4) etsi(0) reserved(127) etsi-identified-organization(0) 7 }

SecurityInfo ::= SEQUENCE {
	protocol OBJECT IDENTIFIER,
	requiredData ANY DEFINED BY protocol,
	optionalData ANY DEFINED BY protocol OPTIONAL
}

SecurityInfos ::= SET OF SecurityInfo

AlgorithmIdentifier ::= SEQUENCE {
	algorithm	OBJECT IDENTIFIER,
	parameters	ANY DEFINED BY algorithm OPTIONAL
}

SubjectPublicKeyInfo ::= SEQUENCE {
	algorithm		AlgorithmIdentifier,
	subjectPublicKey	BIT STRING
}

FieldID ::= SEQUENCE {  
    fieldType   OBJECT IDENTIFIER,
    parameters  ANY DEFINED BY fieldType 
}

ECParameters  ::= SEQUENCE {
    version   ECPVer,
    fieldID   FieldID,
    curve     Curve,
    base      ECPoint,  
    order     INTEGER,  
    cofactor  INTEGER  OPTIONAL 
}

ECPVer ::= INTEGER {ecpVer1(1)}

 Curve  ::= SEQUENCE {
    a     FieldElement,
    b     FieldElement,
    seed  BIT STRING  OPTIONAL 
}

FieldElement ::= OCTET STRING   

ECPoint  ::= OCTET STRING                           


-- ----
-- PACE
-- ----

id-PACE					OBJECT IDENTIFIER ::= { bsi-de protocols(2) smartcard(2) 4 }

id-PACE-DH				OBJECT IDENTIFIER ::= {id-PACE 1}

id-PACE-DH-3DES-CBC-CBC			OBJECT IDENTIFIER ::= {id-PACE-DH 1}
id-PACE-DH-AES-CBC-CMAC-128		OBJECT IDENTIFIER ::= {id-PACE-DH 2}
id-PACE-DH-AES-CBC-CMAC-192		OBJECT IDENTIFIER ::= {id-PACE-DH 3}
id-PACE-DH-AES-CBC-CMAC-256		OBJECT IDENTIFIER ::= {id-PACE-DH 4}

id-PACE-ECDH				OBJECT IDENTIFIER ::= {id-PACE 2}

id-PACE-ECDH-3DES-CBC-CBC			OBJECT IDENTIFIER ::= {id-PACE-ECDH 1}
id-PACE-ECDH-AES-CBC-CMAC-128		OBJECT IDENTIFIER ::= {id-PACE-ECDH 2}
id-PACE-ECDH-AES-CBC-CMAC-192		OBJECT IDENTIFIER ::= {id-PACE-ECDH 3}
id-PACE-ECDH-AES-CBC-CMAC-256		OBJECT IDENTIFIER ::= {id-PACE-ECDH 4}

PACEInfo ::= SEQUENCE {
	protocol	OBJECT IDENTIFIER,
	version		INTEGER,			-- MUST be 1
	parameterId	INTEGER OPTIONAL
}


PACEDomainParameterInfo ::= SEQUENCE {
	protocol 	OBJECT IDENTIFIER,
	domainParameter AlgorithmIdentifier,
	parameterId 	INTEGER OPTIONAL
}

-- ------------------
-- Chip Autentication
-- ------------------

id-CA 				OBJECT IDENTIFIER ::= { bsi-de protocols(2) smartcard(2) 3 }

id-CA-DH 			OBJECT IDENTIFIER ::= {id-CA 1}

id-CA-DH-3DES-CBC-CBC		OBJECT IDENTIFIER ::= {id-CA-DH 1}
id-CA-DH-AES-CBC-CMAC-128	OBJECT IDENTIFIER ::= {id-CA-DH 2}
id-CA-DH-AES-CBC-CMAC-192	OBJECT IDENTIFIER ::= {id-CA-DH 3}
id-CA-DH-AES-CBC-CMAC-256	OBJECT IDENTIFIER ::= {id-CA-DH 4}

id-CA-ECDH			OBJECT IDENTIFIER ::= {id-CA 2}

id-CA-ECDH-3DES-CBC-CBC		OBJECT IDENTIFIER ::= {id-CA-ECDH 1}
id-CA-ECDH-AES-CBC-CMAC-128	OBJECT IDENTIFIER ::= {id-CA-ECDH 2}
id-CA-ECDH-AES-CBC-CMAC-192	OBJECT IDENTIFIER ::= {id-CA-ECDH 3}
id-CA-ECDH-AES-CBC-CMAC-256	OBJECT IDENTIFIER ::= {id-CA-ECDH 4}

ChipAuthenticationInfo ::= SEQUENCE {
	protocol	OBJECT IDENTIFIER ( id-CA-DH | id-CA-ECDH ), 
	version		INTEGER,			 -- MUST be 1 or 2
	keyId		INTEGER OPTIONAL
}

ChipAuthenticationDomainParameterInfo ::= SEQUENCE {
	protocol		OBJECT IDENTIFIER ( id-CA-DH | id-CA-ECDH ),
	domainParameter		AlgorithmIdentifier,
	keyId			INTEGER OPTIONAL
}

id-PK				OBJECT IDENTIFIER ::= { bsi-de protocols(2) smartcard(2) 1 }
id-PK-DH			OBJECT IDENTIFIER ::= {id-PK 1}
id-PK-ECDH			OBJECT IDENTIFIER ::= {id-PK 2}

ChipAuthenticationPublicKeyInfo ::= SEQUENCE {
	protocol			OBJECT IDENTIFIER ( id-PK-DH | id-PK-ECDH ),
	chipAuthenticationPublicKey	SubjectPublicKeyInfo,
	keyId				INTEGER OPTIONAL
}

-- ---------------------
-- Terinal Autentication
-- ---------------------

id-TA			OBJECT IDENTIFIER ::= { bsi-de protocols(2) smartcard(2) 2}

id-TA-RSA		OBJECT IDENTIFIER ::= {id-TA 1}

id-TA-RSA-v1-5-SHA-1	OBJECT IDENTIFIER ::= {id-TA-RSA 1}
id-TA-RSA-v1-5-SHA-256	OBJECT IDENTIFIER ::= {id-TA-RSA 2}
id-TA-RSA-PSS-SHA-1		OBJECT IDENTIFIER ::= {id-TA-RSA 3}
id-TA-RSA-PSS-SHA-256	OBJECT IDENTIFIER ::= {id-TA-RSA 4}

id-TA-ECDSA			OBJECT IDENTIFIER ::= {id-TA 2}
id-TA-ECDSA-SHA-1	OBJECT IDENTIFIER ::= {id-TA-ECDSA 1}
id-TA-ECDSA-SHA-224	OBJECT IDENTIFIER ::= {id-TA-ECDSA 2}
id-TA-ECDSA-SHA-256	OBJECT IDENTIFIER ::= {id-TA-ECDSA 3}

FileID ::= SEQUENCE {
	fid	OCTET STRING (SIZE(2)),
	sfid	OCTET STRING (SIZE(1)) OPTIONAL
}

TerminalAuthenticationInfo ::= SEQUENCE {
	protocol	OBJECT IDENTIFIER,
	version		INTEGER, 			-- MUST be 1 or 2
	efCVCA		FileID OPTIONAL
}

-- -------------------------
-- Restricted Identification
-- -------------------------

id-RI			OBJECT IDENTIFIER ::= { bsi-de protocols(2) smartcard(2) 5}

id-RI-DH		OBJECT IDENTIFIER ::= {id-RI 1}

id-RI-DH-SHA-1		OBJECT IDENTIFIER ::= {id-RI-DH 1}
id-RI-DH-SHA-224	OBJECT IDENTIFIER ::= {id-RI-DH 2}
id-RI-DH-SHA-256	OBJECT IDENTIFIER ::= {id-RI-DH 3}
id-RI-ECDH			OBJECT IDENTIFIER ::= {id-RI 2}
id-RI-ECDH-SHA-1	OBJECT IDENTIFIER ::= {id-RI-ECDH 1}
id-RI-ECDH-SHA-224	OBJECT IDENTIFIER ::= {id-RI-ECDH 2}
id-RI-ECDH-SHA-256	OBJECT IDENTIFIER ::= {id-RI-ECDH 3}

ProtocolParams ::= SEQUENCE {
	version		INTEGER,			-- MUST be 1
	keyId		INTEGER,
	authorizedOnly	BOOLEAN
}

RestrictedIdentificationInfo ::= SEQUENCE {
	protocol	OBJECT IDENTIFIER,
	params		ProtocolParams,
	maxKeyLen	INTEGER OPTIONAL
}

-- ---------------
-- CardInfoLocator
-- ---------------

id-CI		OBJECT IDENTIFIER ::= {bsi-de protocols(2) smartcard(2) 6}

CardInfoLocator ::= SEQUENCE {
	protocol 	OBJECT IDENTIFIER,
	url		IA5String,
	efCardInfo	FileID OPTIONAL
}

ContentType ::= OBJECT IDENTIFIER

EncapsulatedContentInfo ::= SEQUENCE {
  eContentType	ContentType,
  eContent [0]	EXPLICIT OCTET STRING OPTIONAL
}

CMSVersion ::= INTEGER { v0(0), v1(1), v2(2), v3(3), v4(4), v5(5) }
DigestAlgoritmsIdentifiers ::= SET OF DigestAlgorithmIdentifier
DigestAlgorithmIdentifier ::= AlgorithmIdentifier

OtherCertificateFormat ::= SEQUENCE {
       otherCertFormat		OBJECT IDENTIFIER,
       otherCert		ANY DEFINED BY otherCertFormat
}

CertificateChoices ::= CHOICE {
	certificate				Certificate,
	other [3] IMPLICIT			OtherCertificateFormat
}

CertificateSet ::= SET OF CertificateChoices

Certificate  ::=  SEQUENCE  {
     tbsCertificate       TBSCertificate,
     signatureAlgorithm   AlgorithmIdentifier,
     signature            BIT STRING  }

TBSCertificate  ::=  SEQUENCE  {
     version         [0]  Version DEFAULT v1,
     serialNumber         CertificateSerialNumber,
     signature            AlgorithmIdentifier,
     issuer               Name,
     validity             Validity,
     subject              Name,
     subjectPublicKeyInfo SubjectPublicKeyInfo,
     issuerUniqueID  [1]  IMPLICIT UniqueIdentifier OPTIONAL,
                          -- If present, version MUST be v2 or v3
     subjectUniqueID [2]  IMPLICIT UniqueIdentifier OPTIONAL,
                          -- If present, version MUST be v2 or v3
     extensions      [3]  Extensions OPTIONAL
                          -- If present, version MUST be v3 --  }
                          
Version  ::=  INTEGER  {  v1(0), v2(1), v3(2)  }

CertificateSerialNumber  ::=  INTEGER

Name ::= CHOICE { -- only one possibility for now --
      rdnSequence  RDNSequence }

Validity ::= SEQUENCE {
     notBefore      XTime,
     notAfter       XTime  }

XTime ::= CHOICE {
     utcTime        UTCTime,
     generalTime    GeneralizedTime }
     
UniqueIdentifier  ::=  BIT STRING                          

Extension  ::=  SEQUENCE  {
     extnID      OBJECT IDENTIFIER,
     critical    BOOLEAN DEFAULT FALSE,
     extnValue   OCTET STRING  }
     
Extensions  ::=  SEQUENCE SIZE (1..MAX) OF Extension

RelativeDistinguishedName  ::= SET SIZE (1 .. MAX) OF AttributeTypeAndValue

RDNSequence ::= SEQUENCE OF RelativeDistinguishedName

DistinguishedName ::=   RDNSequence

Attribute       ::=     SEQUENCE {
      type              AttributeType,
      values    SET OF AttributeValue
}  -- at least one value is required

AttributeType           ::=  OBJECT IDENTIFIER

AttributeValue          ::=  ANY

AttributeTypeAndValue           ::=     SEQUENCE {
        type    AttributeType,
        value   AttributeValue }

RevocationInfoChoices ::= SET OF RevocationInfoChoice
	
RevocationInfoChoice ::= CHOICE {
	crl 			CertificateList,
        other [1] IMPLICIT	OtherRevocationInfoFormat
}

OtherRevocationInfoFormat ::= SEQUENCE {
	otherRevInfoFormat	OBJECT IDENTIFIER,
        otherRevInfo		ANY DEFINED BY otherRevInfoFormat
}

CertificateList  ::=  SEQUENCE  {
	tbsCertList		TBSCertList,
	signatureAlgorithm	AlgorithmIdentifier,
	signature		BIT STRING
}

TBSCertList  ::=  SEQUENCE  {
	version			Version OPTIONAL,					-- if present, MUST be v2
	signature		AlgorithmIdentifier,
	issuer			Name,
	thisUpdate		XTime,
	nextUpdate		XTime OPTIONAL,
	revokedCertificates	RevokedCertificates OPTIONAL,				-- if present, MUST be v2
	crlExtensions           [0] Extensions OPTIONAL
}

RevokedCertificates ::= SEQUENCE OF RevokedCertificate

RevokedCertificate ::= SEQUENCE	{
		userCertificate		CertificateSerialNumber,
		revocationDate		XTime,
		crlEntryExtensions	Extensions OPTIONAL				-- if present, MUST be v2
}      

SignerInfos ::= SET OF SignerInfo

SignatureValue ::= OCTET STRING

SignedAttribute ::= SEQUENCE {
	attrType	OBJECT IDENTIFIER,
	attrValue	ANY DEFINED BY attrType
}

SignedAttributes ::= SET OF SignedAttribute

SignerInfo ::= SEQUENCE {
 	version			CMSVersion,
	sid			SignerIdentifier,
 	digestAlgorithm		DigestAlgorithmIdentifier,
 	signedAttr [0]	IMPLICIT SignedAttributes,
 	signatureAlgorithm	AlgorithmIdentifier,
 	signature	SignatureValue
}

SignerIdentifier ::= CHOICE {
	issuerAndSerialNumber		IssuerAndSerialNumber,
	subjectKeyIdentifier [0]	SubjectKeyIdentifier
}

SignatureAlgorithmIdentifier ::= AlgorithmIdentifier

IssuerAndSerialNumber ::= SEQUENCE {
        issuer		Name,
        serialNumber	CertificateSerialNumber
}

KeyIdentifier ::= OCTET STRING

SubjectKeyIdentifier ::= KeyIdentifier
       
SignedData ::= SEQUENCE{
 	version			    CMSVersion,
 	digestAlgorithms	DigestAlgoritmsIdentifiers,
 	encapContentInfo	EncapsulatedContentInfo,
 	certificates [0]	IMPLICIT CertificateSet OPTIONAL,
 	crls [1]		    IMPLICIT RevocationInfoChoices OPTIONAL,
 	signerInfos		    SignerInfos
}

ContentInfo ::= SEQUENCE{
 	contentType			ContentType,
    content [0]			EXPLICIT ANY DEFINED BY contentType
} 

-- ------------------------
-- Certificate Description
-- ------------------------

id-extensions	OBJECT IDENTIFIER ::= { bsi-de applications(3) mrtd(1) 3 }

id-description	OBJECT IDENTIFIER ::= { id-extensions 1 }

id-plainFormat OBJECT IDENTIFIER ::= {id-description 1}
PlainTermsOfUsage ::= UTF8String

id-htmlFormat OBJECT IDENTIFIER ::= {id-description 2}
HtmlTermsOfUsage ::= IA5String

id-pdfFormat OBJECT IDENTIFIER ::= {id-description 3}
PdfTermsOfUsage ::= OCTET STRING

CertificateDescription ::= SEQUENCE {
	descriptionType		OBJECT IDENTIFIER,
	issuerName			[1]	UTF8String,
	issuerURL			[2]	PrintableString OPTIONAL,
	subjectName			[3]	UTF8String,
	subjectURL			[4]	PrintableString OPTIONAL,
	termsOfUsage		[5]	ANY DEFINED BY descriptionType,
	redirectURL			[6]	PrintableString OPTIONAL,
	commCertificates	[7] ANY OPTIONAL
}

-- ------------------------
-- CV Certificate
-- ------------------------

-- FIXME. should better use dh *and* ecdh public keys. see BSI TR-03110 --
PublicKey ::= [APPLICATION 73] IMPLICIT SEQUENCE {
	pkID 			OBJECT IDENTIFIER,
	domParaP		[1] ANY DEFINED BY pkID OPTIONAL,
	domParaA		[2] ANY DEFINED BY pkID OPTIONAL,
	domParaB		[3] ANY DEFINED BY pkID OPTIONAL,
	domParaG		[4] ANY DEFINED BY pkID OPTIONAL,
	domParaR		[5] ANY DEFINED BY pkID OPTIONAL,
	domParaY		[6] ANY DEFINED BY pkID OPTIONAL,
	domParaC		[7] ANY DEFINED BY pkID OPTIONAL
}

CertificateHolderAuthorizationTemplate ::= [APPLICATION 76] IMPLICIT SEQUENCE {
	authTerminalID		OBJECT IDENTIFIER,
	chat			[APPLICATION 19] IMPLICIT OCTET STRING
 		
}

DiscretionaryDataTemplate ::= [APPLICATION 19] IMPLICIT SEQUENCE {
	ttID    	OBJECT IDENTIFIER,
	extInfo		ANY DEFINED BY ttID
}

CertificateExtensions ::=  [APPLICATION 5] IMPLICIT SET OF DiscretionaryDataTemplate

CertificateBody ::= SEQUENCE {
		certIdentifier			[APPLICATION 41] IMPLICIT INTEGER (0..127),
 		certAuthRef			[APPLICATION 2] IMPLICIT PrintableString,
		pubKey				PublicKey,
		certHolderRef			[APPLICATION 32] IMPLICIT PrintableString,
		certHolderAuthTemplate		CertificateHolderAuthorizationTemplate,
		certEffectiveDate		[APPLICATION 37] IMPLICIT OCTET STRING,
		certExpirationDate		[APPLICATION 36] IMPLICIT OCTET STRING,
		certExt				ANY DEFINED BY pubKey OPTIONAL
}


CVCertificate  ::= [APPLICATION 33] IMPLICIT SEQUENCE {
	certBody	[APPLICATION 78] IMPLICIT CertificateBody,
	signature	[APPLICATION 55] IMPLICIT OCTET STRING
		
}

-- ------------------------
-- eID Application
-- ------------------------

id-eID OBJECT IDENTIFIER ::= { bsi-de applications(3) 2 }

DocumentType ::= [APPLICATION 1] ICAOString (SIZE (2))

IssuingState ::= [APPLICATION 2] ICAOCountry

DateOfExpiry ::= [APPLICATION 3] Date

GivenNames ::= [APPLICATION 4] UTF8String

FamilyNames ::= [APPLICATION 5] UTF8String

ArtisticName ::= [APPLICATION 6] UTF8String

AcademicTitle ::= [APPLICATION 7] UTF8String

DateOfBirth ::= [APPLICATION 8] Date

PlaceOfBirth ::= [APPLICATION 9] GeneralPlace

Nationality ::= [APPLICATION 10] ICAOCountry

Sex ::= [APPLICATION 11] ICAOSex

OptionalDataR ::= [APPLICATION 12] SET OF OptionalData

PlaceOfResidence ::= [APPLICATION 17] GeneralPlace

CommunityID ::= [APPLICATION 18] OCTET STRING

ResidencePermitI ::= [APPLICATION 19] Text

ResidencePermitII::= [APPLICATION 20] Text

OptionalDataRW ::= [APPLICATION 21] SET OF OptionalData

ICAOString ::= PrintableString (FROM ("A".. "Z" | " "))

ICAOCountry ::= ICAOString (SIZE (1|3)) -- ICAO country code

ICAOSex ::= PrintableString (FROM ("M"|"F"|" "))

Date ::= NumericString (SIZE (8)) -- YYYYMMDD

Place ::= SEQUENCE {
	street		[10] UTF8String OPTIONAL,
	city		[11] UTF8String,
	state		[12] UTF8String OPTIONAL,
	country		[13] ICAOCountry,
	zipcode		[14] PrintableString OPTIONAL
}

GeneralPlace ::= CHOICE {
	structuredPlace	Place,
	freetextPlace	[1] UTF8String,
	noPlaceInfo		[2] UTF8String
}

Text ::= CHOICE {
	uncompressed	[1] UTF8String,
	compressed		[2] OCTET STRING
}

OptionalData ::= SEQUENCE {
	type	OBJECT IDENTIFIER,
	data	ANY DEFINED BY type OPTIONAL
}

id-AuxiliaryData OBJECT IDENTIFIER ::= { bsi-de applications(3) mrtd(1) 4 }

id-DateOfBirth OBJECT IDENTIFIER ::= { id-AuxiliaryData 1 }

id-DateOfExpiry OBJECT IDENTIFIER ::= { id-AuxiliaryData 2 }

id-CommunityID OBJECT IDENTIFIER ::= { id-AuxiliaryData 3 }

id-TransactionData OBJECT IDENTIFIER ::= { id-AuxiliaryData 4 }

ValidityDate ::= [APPLICATION 19] IMPLICIT Date

AgeVerificationDate ::= [APPLICATION 19] IMPLICIT Date

AuxDataTemplate ::= [APPLICATION 19] IMPLICIT SEQUENCE {
	auxID    	OBJECT IDENTIFIER,
	extInfo		ANY DEFINED BY auxID
}

AuxiliaryAuthenticatedData ::=  [APPLICATION 7] IMPLICIT SET OF AuxDataTemplate

-- ------------------------
-- PACE CCID-MAPPING TR3119
-- ------------------------

PACECapabilities ::= SEQUENCE {
	capabilityPACE		[1] BOOLEAN,
	capabilityEID		[2] BOOLEAN,
	capabilityESign		[3] BOOLEAN,
	capabilityDestroy	[4] BOOLEAN
}

EstablishPACEChannelInput ::= SEQUENCE {
	passwordID				[1] INTEGER,
	transmittedPassword		[2] NumericString OPTIONAL,
	cHAT					[3] OCTET STRING OPTIONAL,
	certificateDescription	[4] CertificateDescription OPTIONAL,
	hashOID					[5] OBJECT IDENTIFIER OPTIONAL,
	cHATrequired			[6] OCTET STRING OPTIONAL,
	cHAToptional			[7] OCTET STRING OPTIONAL,
	transactionInfo			[8] UTF8String OPTIONAL,
	transactionInfoHashOID	[9] OBJECT IDENTIFIER OPTIONAL
}

EstablishPACEChannelOutput ::= SEQUENCE {
	errorCode			[1] OCTET STRING (SIZE(4)),
	statusMSESetAT		[2] OCTET STRING (SIZE(2)),
	efCardAccess		[3] SecurityInfos,
	idPICC				[4] OCTET STRING OPTIONAL,
	curCAR				[5]	OCTET STRING OPTIONAL,
	prevCAR				[6] OCTET STRING OPTIONAL,
	cHATout				[7] OCTET STRING OPTIONAL
}	


END
