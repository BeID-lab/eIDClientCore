/*
 * Copyright (C) 2012 Bundesdruckerei GmbH
 */

CVCertTest DEFINITIONS ::=

BEGIN

/* FIXME. should better use dh *and* ecdh public keys. see BSI TR-03110 */
PublicKey ::= [APPLICATION 73] IMPLICIT SEQUENCE {
	pkID 			OBJECT IDENTIFIER,
	domParaP		[1] ANY DEFINED BY pkID OPTIONAL,
	domParaA		[2] ANY DEFINED BY pkID OPTIONAL,
	domParaB		[3] ANY DEFINED BY pkID OPTIONAL,
	domParaG		[4] ANY DEFINED BY pkID OPTIONAL,
	domParaR		[5] ANY DEFINED BY pkID OPTIONAL,
	domParaY		[6] ANY DEFINED BY pkID OPTIONAL,
	domParaC		[7] ANY DEFINED BY pkID OPTIONAL
}

CertificateHolderAuthorizationTemplate ::= [APPLICATION 76] IMPLICIT SEQUENCE {
	authTerminalID		OBJECT IDENTIFIER,
	chat			[APPLICATION 19] IMPLICIT OCTET STRING
 		
}

DiscretionaryDataTemplate ::= [APPLICATION 19] IMPLICIT SEQUENCE {
	ttID    	OBJECT IDENTIFIER,
	extInfo		ANY DEFINED BY ttID
}

CertificateExtensions ::=  [APPLICATION 5] IMPLICIT SET OF DiscretionaryDataTemplate

CertificateBody ::= SEQUENCE {
		certIdentifier			[APPLICATION 41] IMPLICIT INTEGER (0..127),
 		certAuthRef			[APPLICATION 2] IMPLICIT PrintableString,
		pubKey				PublicKey,
		certHolderRef			[APPLICATION 32] IMPLICIT PrintableString,
		certHolderAuthTemplate		CertificateHolderAuthorizationTemplate,
		certEffectiveDate		[APPLICATION 37] IMPLICIT OCTET STRING,
		certExpirationDate		[APPLICATION 36] IMPLICIT OCTET STRING,
		certExt				ANY DEFINED BY pubKey OPTIONAL
}


CVCertificate  ::= [APPLICATION 33] IMPLICIT SEQUENCE {
	certBody	[APPLICATION 78] IMPLICIT CertificateBody,
	signature	[APPLICATION 55] IMPLICIT OCTET STRING
		
}

END
